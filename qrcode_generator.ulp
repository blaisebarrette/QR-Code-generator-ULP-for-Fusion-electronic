// QR Code Generator for Eagle/Fusion Electronics
// This ULP generates QR codes directly on PCB layers
// Version 1.2.0 - fully self-contained (native QR generation, embedded
//                 localization, no remote calls, no external file imports).
//
// Starting with this release, the ULP is a single self-contained file:
//   - QR Code generation runs entirely in pure ULP (no Python server).
//   - All UI text translations are embedded in this file (no localization.csv).
//   - The legacy version-check feature has been removed; the previous
//     versions.csv mechanism is preserved server-side only for users still
//     running ULP releases earlier than 1.2.0.

#usage "en: <b>QR Code Generator for Fusion Electronics</b>\n"
       "<p>"
       "Generate QR codes directly in PCB, Schematic, Symbol, and Footprint contexts with customizable sizes.<br>"
       "The QR code will be automatically placed in the upper-left quadrant from the origin.</p>"
       "<p><b>Usage:</b><br>"
       "1. Run the ULP and enter your URL<br>"
       "2. Select the size and unit (mils, inches, or mm)<br>"
       "3. Choose the destination layer</p>"
       "<p>GitHub: <a href='https://github.com/blaisebarrette/QRCode-ULP-for-Fusion-electronics'>QRCode-ULP-for-Fusion-electronics</a></p>"
       "<author>Author: <b>Blaise Barrette</b></author>",
       
       "fr: <b>Générateur de QR Code pour Fusion Electronics</b>\n"
       "<p>"
       "Générez des QR codes directement dans les contextes PCB, Schéma, Symbole et Encombrement avec des tailles personnalisables.<br>"
       "Le QR code sera automatiquement placé dans le quadrant supérieur gauche à partir de l'origine.</p>"
       "<p><b>Utilisation :</b><br>"
       "1. Exécutez l'ULP et entrez votre URL<br>"
       "2. Sélectionnez la taille et l'unité (mils, pouces ou mm)<br>"
       "3. Choisissez la couche de destination</p>"
       "<p>GitHub: <a href='https://github.com/blaisebarrette/QRCode-ULP-for-Fusion-electronics'>QRCode-ULP-for-Fusion-electronics</a></p>"
       "<author>Auteur : <b>Blaise Barrette</b></author>",
       
       "de: <b>QR-Code-Generator für Fusion Electronics</b>\n"
       "<p>"
       "Generieren Sie QR-Codes direkt in PCB-, Schaltplan-, Symbol- und Footprint-Kontexten mit anpassbaren Größen.<br>"
       "Der QR-Code wird automatisch im oberen linken Quadranten vom Ursprung platziert.</p>"
       "<p><b>Verwendung:</b><br>"
       "1. Führen Sie das ULP aus und geben Sie Ihre URL ein<br>"
       "2. Wählen Sie die Größe und Einheit (mils, Zoll oder mm)<br>"
       "3. Wählen Sie die Zielebene</p>"
       "<p>GitHub: <a href='https://github.com/blaisebarrette/QRCode-ULP-for-Fusion-electronics'>QRCode-ULP-for-Fusion-electronics</a></p>"
       "<author>Autor: <b>Blaise Barrette</b></author>",
       
       "es: <b>Generador de códigos QR para Fusion Electronics</b>\n"
       "<p>"
       "Genere códigos QR directamente en contextos de PCB, Esquemático, Símbolo y Huella con tamaños personalizables.<br>"
       "El código QR se colocará automáticamente en el cuadrante superior izquierdo desde el origen.</p>"
       "<p><b>Uso:</b><br>"
       "1. Ejecute el ULP e ingrese su URL<br>"
       "2. Seleccione el tamaño y la unidad (mils, pulgadas o mm)<br>"
       "3. Elija la capa de destino</p>"
       "<p>GitHub: <a href='https://github.com/blaisebarrette/QRCode-ULP-for-Fusion-electronics'>QRCode-ULP-for-Fusion-electronics</a></p>"
       "<author>Autor: <b>Blaise Barrette</b></author>",
       
       "it: <b>Generatore di codici QR per Fusion Electronics</b>\n"
       "<p>"
       "Genera codici QR direttamente nei contesti PCB, Schema, Simbolo e Impronta con dimensioni personalizzabili.<br>"
       "Il codice QR verrà posizionato automaticamente nel quadrante superiore sinistro dall'origine.</p>"
       "<p><b>Utilizzo:</b><br>"
       "1. Esegui l'ULP e inserisci il tuo URL<br>"
       "2. Seleziona la dimensione e l'unità (mils, pollici o mm)<br>"
       "3. Scegli il layer di destinazione</p>"
       "<p>GitHub: <a href='https://github.com/blaisebarrette/QRCode-ULP-for-Fusion-electronics'>QRCode-ULP-for-Fusion-electronics</a></p>"
       "<author>Autore: <b>Blaise Barrette</b></author>",
       
       "ja: <b>QRコードジェネレーター for Fusion Electronics</b>\n"
       "<p>"
       "PCB、回路図、シンボル、フットプリントのコンテキストで、カスタマイズ可能なサイズのQRコードを直接生成します。<br>"
       "QRコードは原点から左上の象限に自動的に配置されます。</p>"
       "<p><b>使用方法：</b><br>"
       "1. ULPを実行してURLを入力<br>"
       "2. サイズと単位を選択（mils、インチ、mm）<br>"
       "3. 配置するレイヤーを選択</p>"
       "<p>GitHub: <a href='https://github.com/blaisebarrette/QRCode-ULP-for-Fusion-electronics'>QRCode-ULP-for-Fusion-electronics</a></p>"
       "<author>作者: <b>Blaise Barrette</b></author>",
       
       "ko: <b>QR 코드 생성기 for Fusion Electronics</b>\n"
       "<p>"
       "PCB, 회로도, 심볼, 풋프린트 컨텍스트에서 사용자 지정 크기로 QR 코드를 직접 생성합니다.<br>"
       "QR 코드는 원점에서 좌측 상단 사분면에 자동으로 배치됩니다.</p>"
       "<p><b>사용법:</b><br>"
       "1. ULP를 실행하고 URL 입력<br>"
       "2. 크기와 단위 선택 (mils, 인치, mm)<br>"
       "3. 대상 레이어 선택</p>"
       "<p>GitHub: <a href='https://github.com/blaisebarrette/QRCode-ULP-for-Fusion-electronics'>QRCode-ULP-for-Fusion-electronics</a></p>"
       "<author>작성자: <b>Blaise Barrette</b></author>",
       
       "pl: <b>Generator kodów QR dla Fusion Electronics</b>\n"
       "<p>"
       "Generuj kody QR bezpośrednio w kontekstach PCB, Schematu, Symbolu i Footprintu z dostosowywanymi rozmiarami.<br>"
       "Kod QR zostanie automatycznie umieszczony w lewym górnym kwadrancie od początku układu.</p>"
       "<p><b>Użycie:</b><br>"
       "1. Uruchom ULP i wprowadź swój URL<br>"
       "2. Wybierz rozmiar i jednostkę (mils, cale lub mm)<br>"
       "3. Wybierz warstwę docelową</p>"
       "<p>GitHub: <a href='https://github.com/blaisebarrette/QRCode-ULP-for-Fusion-electronics'>QRCode-ULP-for-Fusion-electronics</a></p>"
       "<author>Autor: <b>Blaise Barrette</b></author>",
       
       "pt: <b>Gerador de código QR para Fusion Electronics</b>\n"
       "<p>"
       "Gere códigos QR diretamente nos contextos de PCB, Esquemático, Símbolo e Footprint com tamanhos personalizáveis.<br>"
       "O código QR será automaticamente colocado no quadrante superior esquerdo a partir da origem.</p>"
       "<p><b>Uso:</b><br>"
       "1. Execute o ULP e insira sua URL<br>"
       "2. Selecione o tamanho e a unidade (mils, polegadas ou mm)<br>"
       "3. Escolha a camada de destino</p>"
       "<p>GitHub: <a href='https://github.com/blaisebarrette/QRCode-ULP-for-Fusion-electronics'>QRCode-ULP-for-Fusion-electronics</a></p>"
       "<author>Autor: <b>Blaise Barrette</b></author>",
       
       "zh: <b>二维码生成器 for Fusion Electronics</b>\n"
       "<p>"
       "在PCB、原理图、符号和封装环境中直接生成可自定义大小的二维码。<br>"
       "二维码将自动放置在原点的左上象限。</p>"
       "<p><b>使用方法：</b><br>"
       "1. 运行ULP并输入URL<br>"
       "2. 选择大小和单位（mils、英寸或毫米）<br>"
       "3. 选择目标层</p>"
       "<p>GitHub: <a href='https://github.com/blaisebarrette/QRCode-ULP-for-Fusion-electronics'>QRCode-ULP-for-Fusion-electronics</a></p>"
       "<author>作者: <b>Blaise Barrette</b></author>",
       
       "tr: <b>QR Kod Üreteci for Fusion Electronics</b>\n"
       "<p>"
       "PCB, Şematik, Sembol ve Footprint bağlamlarında özelleştirilebilir boyutlarla doğrudan QR kodları oluşturun.<br>"
       "QR kodu otomatik olarak başlangıç noktasından sol üst kadrana yerleştirilecektir.</p>"
       "<p><b>Kullanım:</b><br>"
       "1. ULP'yi çalıştırın ve URL'nizi girin<br>"
       "2. Boyutu ve birimi seçin (mils, inç veya mm)<br>"
       "3. Hedef katmanı seçin</p>"
       "<p>GitHub: <a href='https://github.com/blaisebarrette/QRCode-ULP-for-Fusion-electronics'>QRCode-ULP-for-Fusion-electronics</a></p>"
       "<author>Yazar: <b>Blaise Barrette</b></author>"

#require 4.11  // 4.11 is the minimum Eagle version required for this ULP

// =========================================================================
// Native QR Code generation engine (inlined for single-file distribution)
// -------------------------------------------------------------------------
// This block replaces the previous Python-server dependency. It implements
// QR Code generation entirely in ULP for versions V1..V10, ECC level L,
// byte mode. The architecture is designed for future extension to V11..V40
// and ECC levels M/Q/H without changing the public API.
//
// Public API:
//   int qrGenerate(string data, int ecc, int mode);
//     -> on success: number of "0/1" rows written into QR_OUTPUT_LINES[]
//     -> on failure: -1 (see QR_LAST_ERROR for diagnostics)
//
// Sections (each was previously a separate include):
//   1. Tables and constants    (was qr_tables.ulp)
//   2. GF(256) + Reed-Solomon  (was qr_gf256.ulp)
//   3. Data encoding pipeline  (was qr_encode.ulp)
//   4. Matrix construction     (was qr_matrix.ulp)
//   5. Public API              (was qr_core.ulp)
//
// All large working buffers are kept as globals because ULP user-defined
// functions pass parameters by value (modifications inside a function do
// not propagate to the caller).
// =========================================================================

// -------------------------------------------------------------------------
// 1. Tables and constants
// -------------------------------------------------------------------------

// ECC level codes (placement-bit values are encoded in qrEccBits()).
enum {
    ECC_L = 0,
    ECC_M = 1,
    ECC_Q = 2,
    ECC_H = 3
};

// Encoding mode codes.
enum {
    MODE_BYTE     = 0,
    MODE_NUMERIC  = 1,
    MODE_ALPHANUM = 2
};

// Highest version supported in this build.
int QR_MAX_VERSION = 10;

// EC codewords per block, level L, V1..V10
int QR_ECP_L[]  = { 7, 10, 15, 20, 26, 18, 20, 24, 30, 18 };
// Group 1: number of blocks, level L, V1..V10
int QR_G1C_L[]  = { 1,  1,  1,  1,  1,  2,  2,  2,  2,  2 };
// Group 1: data codewords per block, level L, V1..V10
int QR_G1D_L[]  = {19, 34, 55, 80,108, 68, 78, 97,116, 68 };
// Group 2: number of blocks, level L, V1..V10 (0 = no group 2)
int QR_G2C_L[]  = { 0,  0,  0,  0,  0,  0,  0,  0,  0,  2 };
// Group 2: data codewords per block, level L, V1..V10
int QR_G2D_L[]  = { 0,  0,  0,  0,  0,  0,  0,  0,  0, 69 };

// Alignment pattern center positions per version.
// V1     : 0 patterns (none, only finder corners).
// V2..V6 : 2 positions [first, last].
// V7..V10: 3 positions [first, middle, last].
int QR_ALIGN_COUNT[] = { 0, 2, 2, 2, 2, 2, 3, 3, 3, 3 };
int QR_ALIGN_POS_FLAT[] = {
    0, 0, 0,    // V1
    6,18, 0,    // V2
    6,22, 0,    // V3
    6,26, 0,    // V4
    6,30, 0,    // V5
    6,34, 0,    // V6
    6,22,38,    // V7
    6,24,42,    // V8
    6,26,46,    // V9
    6,28,50     // V10
};

// BCH encoding constants.
int QR_BCH_GEN_FORMAT  = 0x537;   // x^10+x^8+x^5+x^4+x^2+x+1
int QR_BCH_MASK_FORMAT = 0x5412;  // XOR mask applied to format info
int QR_BCH_GEN_VERSION = 0x1F25;  // x^12+x^11+x^10+x^9+x^8+x^5+x^2+1 (used for V7+)

// GF(256) primitive polynomial: x^8+x^4+x^3+x^2+1 (QR Code standard)
int QR_GF_PRIM = 0x11D;

// Padding bytes for byte mode (alternating).
int QR_PAD_BYTE_1 = 0xEC;
int QR_PAD_BYTE_2 = 0x11;

// Returns total data codewords for the given version and ECC level,
// or -1 if not supported in this build.
int qrDataCodewords(int version, int ecc) {
    if (ecc != ECC_L) return -1;
    if (version < 1 || version > QR_MAX_VERSION) return -1;
    int v = version - 1;
    return QR_G1C_L[v] * QR_G1D_L[v] + QR_G2C_L[v] * QR_G2D_L[v];
}

// Returns EC codewords per block for given version and ECC level.
int qrEcPerBlock(int version, int ecc) {
    if (ecc != ECC_L) return -1;
    if (version < 1 || version > QR_MAX_VERSION) return -1;
    return QR_ECP_L[version - 1];
}

// Block decomposition accessors.
int qrG1Count(int version, int ecc) {
    if (ecc != ECC_L) return -1;
    return QR_G1C_L[version - 1];
}
int qrG1DataPerBlock(int version, int ecc) {
    if (ecc != ECC_L) return -1;
    return QR_G1D_L[version - 1];
}
int qrG2Count(int version, int ecc) {
    if (ecc != ECC_L) return -1;
    return QR_G2C_L[version - 1];
}
int qrG2DataPerBlock(int version, int ecc) {
    if (ecc != ECC_L) return -1;
    return QR_G2D_L[version - 1];
}
int qrTotalBlocks(int version, int ecc) {
    return qrG1Count(version, ecc) + qrG2Count(version, ecc);
}

// Total codewords (data + EC) used for module placement.
int qrTotalCodewords(int version, int ecc) {
    int data   = qrDataCodewords(version, ecc);
    int blocks = qrTotalBlocks(version, ecc);
    int ec     = qrEcPerBlock(version, ecc);
    return data + blocks * ec;
}

// Matrix size for a version: N = 21 + 4*(V-1).
int qrMatrixSize(int version) {
    return 21 + 4 * (version - 1);
}

// Character count indicator length in bits, per mode and version.
// Byte mode: 8 bits for V1..V9, 16 bits for V10..V40.
int qrCharCountBits(int mode, int version) {
    if (mode == MODE_BYTE) {
        if (version <= 9) return 8;
        return 16;
    }
    return -1;
}

// Mode indicator (4 bits).
int qrModeIndicator(int mode) {
    if (mode == MODE_BYTE)     return 0x4;
    if (mode == MODE_NUMERIC)  return 0x1;
    if (mode == MODE_ALPHANUM) return 0x2;
    return -1;
}

// Number of alignment-pattern center positions for the given version.
int qrAlignCount(int version) {
    if (version < 1 || version > QR_MAX_VERSION) return 0;
    return QR_ALIGN_COUNT[version - 1];
}

// Get an alignment-pattern center position by index (0..qrAlignCount-1).
int qrAlignPos(int version, int index) {
    if (version < 1 || version > QR_MAX_VERSION) return -1;
    if (index < 0 || index >= QR_ALIGN_COUNT[version - 1]) return -1;
    return QR_ALIGN_POS_FLAT[(version - 1) * 3 + index];
}

// 2-bit ECC code for format info.
int qrEccBits(int ecc) {
    if (ecc == ECC_L) return 0x1;  // 01
    if (ecc == ECC_M) return 0x0;  // 00
    if (ecc == ECC_Q) return 0x3;  // 11
    if (ecc == ECC_H) return 0x2;  // 10
    return -1;
}

// -------------------------------------------------------------------------
// 2. GF(256) arithmetic and Reed-Solomon encoding
// -------------------------------------------------------------------------

// Galois field log/antilog tables (built once by qrGfInit()).
// QR_GF_EXP is doubled (length 512) so that gfMul can avoid a modulo.
int QR_GF_LOG[];
int QR_GF_EXP[];
int QR_GF_INITIALIZED = 0;

// Reed-Solomon working buffers.
int QR_RS_DIVISOR[];
int QR_RS_DIVISOR_LEN = 0;
int QR_RS_ECC[];

// Data codewords buffer (populated by the encoding stage; consumed by the
// Reed-Solomon encoder and the interleaver).
int QR_CODEWORDS[];
int QR_CODEWORDS_LEN = 0;

// Build the log and antilog tables for GF(256) using QR_GF_PRIM.
void qrGfInit() {
    if (QR_GF_INITIALIZED) return;
    int i;
    for (i = 0; i < 256; i++) QR_GF_LOG[i] = 0;
    int x = 1;
    for (i = 0; i < 255; i++) {
        QR_GF_EXP[i] = x;
        QR_GF_LOG[x] = i;
        x = x << 1;
        if (x & 0x100) x = x ^ QR_GF_PRIM;
    }
    for (i = 255; i < 512; i++) {
        QR_GF_EXP[i] = QR_GF_EXP[i - 255];
    }
    QR_GF_INITIALIZED = 1;
}

// GF(256) multiplication.
int qrGfMul(int a, int b) {
    if (a == 0 || b == 0) return 0;
    return QR_GF_EXP[QR_GF_LOG[a & 0xFF] + QR_GF_LOG[b & 0xFF]];
}

// Build the Reed-Solomon divisor polynomial of degree n into
// QR_RS_DIVISOR (length n; the leading coefficient 1 is implicit).
void qrRsBuildDivisor(int n) {
    int i, j;
    for (i = 0; i < n; i++) QR_RS_DIVISOR[i] = 0;
    QR_RS_DIVISOR[n - 1] = 1;
    int root = 1;
    for (i = 0; i < n; i++) {
        for (j = 0; j < n; j++) {
            QR_RS_DIVISOR[j] = qrGfMul(QR_RS_DIVISOR[j], root);
            if (j + 1 < n) QR_RS_DIVISOR[j] = QR_RS_DIVISOR[j] ^ QR_RS_DIVISOR[j + 1];
        }
        root = qrGfMul(root, 2);
    }
    QR_RS_DIVISOR_LEN = n;
}

// Reed-Solomon encode one block.
// Reads dataLen bytes from QR_CODEWORDS[dataStart..dataStart+dataLen-1]
// and writes n EC bytes into QR_RS_ECC[0..n-1] using QR_RS_DIVISOR.
//
// (ULP user-defined functions cannot take array parameters, so this
// reads directly from the QR_CODEWORDS global.)
void qrRsEncodeBlock(int dataStart, int dataLen, int n) {
    int i, j;
    for (i = 0; i < n; i++) QR_RS_ECC[i] = 0;
    for (i = 0; i < dataLen; i++) {
        int factor = (QR_CODEWORDS[dataStart + i] & 0xFF) ^ QR_RS_ECC[0];
        for (j = 0; j < n - 1; j++) {
            QR_RS_ECC[j] = QR_RS_ECC[j + 1];
        }
        QR_RS_ECC[n - 1] = 0;
        for (j = 0; j < n; j++) {
            QR_RS_ECC[j] = QR_RS_ECC[j] ^ qrGfMul(factor, QR_RS_DIVISOR[j]);
        }
    }
}

// -------------------------------------------------------------------------
// 3. Data encoding pipeline (bit stream -> codewords -> blocks -> EC -> interleave)
// -------------------------------------------------------------------------

// Bit stream
int QR_BITS[];
int QR_BIT_COUNT = 0;

// Per-block decomposition: each block is a (offset, length) pair into QR_CODEWORDS.
int QR_BLOCK_OFFSET[];
int QR_BLOCK_LEN[];
int QR_BLOCK_COUNT = 0;
// EC bytes of all blocks concatenated, EC_PER_BLOCK bytes per block.
int QR_BLOCK_EC[];
int QR_EC_PER_BLOCK = 0;

// Final interleaved codeword sequence (data + EC).
int QR_INTERLEAVED[];
int QR_INTERLEAVED_LEN = 0;

// Append numBits of value (MSB first) to the bit stream.
void qrAppendBits(int value, int numBits) {
    int i;
    for (i = numBits - 1; i >= 0; i--) {
        QR_BITS[QR_BIT_COUNT] = (value >> i) & 1;
        QR_BIT_COUNT++;
    }
}

// Encode the input string in byte mode (mode indicator + char count + bytes).
// Returns 0 on success, -1 on overflow.
int qrEncodeByteMode(string data, int version) {
    QR_BIT_COUNT = 0;
    int dataLen = strlen(data);
    qrAppendBits(qrModeIndicator(MODE_BYTE), 4);
    int ccBits = qrCharCountBits(MODE_BYTE, version);
    if (dataLen >= (1 << ccBits)) return -1;
    qrAppendBits(dataLen, ccBits);
    int i;
    for (i = 0; i < dataLen; i++) {
        qrAppendBits(data[i] & 0xFF, 8);
    }
    return 0;
}

// Mode dispatcher. Currently only MODE_BYTE is implemented; numeric/alphanum
// will plug in here without changing any other section.
int qrEncodeData(string data, int mode, int version) {
    if (mode == MODE_BYTE) return qrEncodeByteMode(data, version);
    return -1;
}

// Choose the smallest version V1..QR_MAX_VERSION that fits the encoded data.
int qrChooseVersion(int dataLen, int mode, int ecc) {
    int v;
    for (v = 1; v <= QR_MAX_VERSION; v++) {
        int capBits = qrDataCodewords(v, ecc) * 8;
        if (capBits < 0) continue;
        int needed = 4 + qrCharCountBits(mode, v) + dataLen * 8;
        if (needed <= capBits) return v;
    }
    return -1;
}

// Pad the bit stream with terminator + byte padding, then pack to bytes
// and append alternating 0xEC/0x11 padding bytes up to totalDataCodewords.
void qrPadAndPack(int totalDataCodewords) {
    int totalBits = totalDataCodewords * 8;
    int term = 4;
    if (QR_BIT_COUNT + term > totalBits) term = totalBits - QR_BIT_COUNT;
    int i;
    for (i = 0; i < term; i++) QR_BITS[QR_BIT_COUNT++] = 0;

    while ((QR_BIT_COUNT % 8) != 0) QR_BITS[QR_BIT_COUNT++] = 0;

    int byteCount = QR_BIT_COUNT / 8;
    int b;
    for (b = 0; b < byteCount; b++) {
        int v = 0;
        for (i = 0; i < 8; i++) v = (v << 1) | QR_BITS[b * 8 + i];
        QR_CODEWORDS[b] = v;
    }
    int useEc = 1;
    while (byteCount < totalDataCodewords) {
        QR_CODEWORDS[byteCount++] = useEc ? QR_PAD_BYTE_1 : QR_PAD_BYTE_2;
        useEc = !useEc;
    }
    QR_CODEWORDS_LEN = totalDataCodewords;
}

// Split QR_CODEWORDS into blocks per the (group1, group2) structure.
void qrSplitBlocks(int version, int ecc) {
    int g1c = qrG1Count(version, ecc);
    int g1d = qrG1DataPerBlock(version, ecc);
    int g2c = qrG2Count(version, ecc);
    int g2d = qrG2DataPerBlock(version, ecc);
    QR_BLOCK_COUNT = g1c + g2c;
    int off = 0;
    int b;
    for (b = 0; b < g1c; b++) {
        QR_BLOCK_OFFSET[b] = off;
        QR_BLOCK_LEN[b]    = g1d;
        off += g1d;
    }
    for (b = 0; b < g2c; b++) {
        QR_BLOCK_OFFSET[g1c + b] = off;
        QR_BLOCK_LEN[g1c + b]    = g2d;
        off += g2d;
    }
}

// Compute Reed-Solomon EC for every block.
void qrComputeEcAllBlocks(int version, int ecc) {
    int n = qrEcPerBlock(version, ecc);
    QR_EC_PER_BLOCK = n;
    qrRsBuildDivisor(n);
    int b, j;
    for (b = 0; b < QR_BLOCK_COUNT; b++) {
        qrRsEncodeBlock(QR_BLOCK_OFFSET[b], QR_BLOCK_LEN[b], n);
        for (j = 0; j < n; j++) {
            QR_BLOCK_EC[b * n + j] = QR_RS_ECC[j];
        }
    }
}

// Interleave data and EC codewords into QR_INTERLEAVED in QR Code order.
void qrInterleave() {
    int i, b;
    int maxDataLen = 0;
    for (b = 0; b < QR_BLOCK_COUNT; b++) {
        if (QR_BLOCK_LEN[b] > maxDataLen) maxDataLen = QR_BLOCK_LEN[b];
    }
    int out = 0;
    for (i = 0; i < maxDataLen; i++) {
        for (b = 0; b < QR_BLOCK_COUNT; b++) {
            if (i < QR_BLOCK_LEN[b]) {
                QR_INTERLEAVED[out++] = QR_CODEWORDS[QR_BLOCK_OFFSET[b] + i];
            }
        }
    }
    int n = QR_EC_PER_BLOCK;
    for (i = 0; i < n; i++) {
        for (b = 0; b < QR_BLOCK_COUNT; b++) {
            QR_INTERLEAVED[out++] = QR_BLOCK_EC[b * n + i];
        }
    }
    QR_INTERLEAVED_LEN = out;
}

// -------------------------------------------------------------------------
// 4. Matrix construction, masking, format/version info, serialization
// -------------------------------------------------------------------------

// Matrix state. Flat NxN buffers indexed as r*QR_SIZE + c.
int QR_MATRIX[];
int QR_FN_MASK[];   // 1 = function module (locked), 0 = data module
int QR_SIZE = 0;
int QR_VERSION = 0;
int QR_ECC = 0;

// Output: one "0/1" string per matrix row.
string QR_OUTPUT_LINES[];
int QR_OUTPUT_LINES_COUNT = 0;

// Module accessors
void qrSetMod(int r, int c, int v) {
    QR_MATRIX[r * QR_SIZE + c] = v ? 1 : 0;
}
int qrGetMod(int r, int c) {
    return QR_MATRIX[r * QR_SIZE + c];
}
void qrMarkFn(int r, int c) {
    QR_FN_MASK[r * QR_SIZE + c] = 1;
}
int qrIsFn(int r, int c) {
    return QR_FN_MASK[r * QR_SIZE + c];
}
void qrSetFn(int r, int c, int v) {
    qrSetMod(r, c, v);
    qrMarkFn(r, c);
}

void qrInitMatrix(int version) {
    QR_VERSION = version;
    QR_SIZE = qrMatrixSize(version);
    int total = QR_SIZE * QR_SIZE;
    int i;
    for (i = 0; i < total; i++) {
        QR_MATRIX[i]  = 0;
        QR_FN_MASK[i] = 0;
    }
}

// Draw the 7x7 finder block at top-left corner (br, bc) plus its 1-module
// inside-edge separator.
void qrDrawFinder(int br, int bc) {
    int dr, dc;
    for (dr = -1; dr <= 7; dr++) {
        for (dc = -1; dc <= 7; dc++) {
            int r = br + dr;
            int c = bc + dc;
            if (r < 0 || r >= QR_SIZE || c < 0 || c >= QR_SIZE) continue;
            int v = 0;
            if (dr >= 0 && dr <= 6 && dc >= 0 && dc <= 6) {
                int onBorder = (dr == 0 || dr == 6 || dc == 0 || dc == 6);
                int inCenter = (dr >= 2 && dr <= 4 && dc >= 2 && dc <= 4);
                if (onBorder || inCenter) v = 1;
            }
            qrSetFn(r, c, v);
        }
    }
}

void qrPlaceFinders() {
    qrDrawFinder(0, 0);                       // top-left
    qrDrawFinder(0, QR_SIZE - 7);             // top-right
    qrDrawFinder(QR_SIZE - 7, 0);             // bottom-left
}

void qrPlaceTiming() {
    int i;
    for (i = 8; i < QR_SIZE - 8; i++) {
        int v = (i & 1) == 0 ? 1 : 0;
        qrSetFn(6, i, v);
        qrSetFn(i, 6, v);
    }
}

// Draw a 5x5 alignment pattern centered at (cr, cc).
void qrDrawAlignment(int cr, int cc) {
    int dr, dc;
    for (dr = -2; dr <= 2; dr++) {
        for (dc = -2; dc <= 2; dc++) {
            int r = cr + dr;
            int c = cc + dc;
            int onBorder = (dr == -2 || dr == 2 || dc == -2 || dc == 2);
            int isCenter = (dr == 0 && dc == 0);
            int v = (onBorder || isCenter) ? 1 : 0;
            qrSetFn(r, c, v);
        }
    }
}

void qrPlaceAlignments(int version) {
    int n = qrAlignCount(version);
    if (n == 0) return;
    int i, j;
    for (i = 0; i < n; i++) {
        for (j = 0; j < n; j++) {
            // Skip the 3 finder corners.
            if (i == 0 && j == 0) continue;
            if (i == 0 && j == n - 1) continue;
            if (i == n - 1 && j == 0) continue;
            int cr = qrAlignPos(version, i);
            int cc = qrAlignPos(version, j);
            qrDrawAlignment(cr, cc);
        }
    }
}

// Format / version info reservations
void qrReserveFormatInfo() {
    int i;
    for (i = 0; i <= 8; i++) {
        if (i != 6) qrMarkFn(8, i);
        if (i != 6) qrMarkFn(i, 8);
    }
    for (i = QR_SIZE - 8; i < QR_SIZE; i++) {
        qrMarkFn(8, i);
    }
    for (i = QR_SIZE - 7; i < QR_SIZE; i++) {
        qrMarkFn(i, 8);
    }
    qrSetFn(QR_SIZE - 8, 8, 1);
}

void qrReserveVersionInfo(int version) {
    if (version < 7) return;
    int r, c;
    for (r = 0; r < 6; r++) {
        for (c = QR_SIZE - 11; c < QR_SIZE - 8; c++) {
            qrMarkFn(r, c);
        }
    }
    for (r = QR_SIZE - 11; r < QR_SIZE - 8; r++) {
        for (c = 0; c < 6; c++) {
            qrMarkFn(r, c);
        }
    }
}

// Place data codewords following the QR Code zigzag convention.
void qrPlaceDataCodewords() {
    int totalBits = QR_INTERLEAVED_LEN * 8;
    int i = 0;
    int right = QR_SIZE - 1;
    while (right >= 1) {
        if (right == 6) right = 5;  // skip the timing column
        int vert;
        for (vert = 0; vert < QR_SIZE; vert++) {
            int j;
            for (j = 0; j < 2; j++) {
                int x = right - j;
                int upward = (((right + 1) & 2) == 0);
                int y = upward ? (QR_SIZE - 1 - vert) : vert;
                if (qrIsFn(y, x) == 0) {
                    int bit = 0;
                    if (i < totalBits) {
                        int byteIndex = i / 8;
                        int bitIndex  = 7 - (i & 7);
                        bit = (QR_INTERLEAVED[byteIndex] >> bitIndex) & 1;
                        i++;
                    }
                    qrSetMod(y, x, bit);
                }
            }
        }
        right = right - 2;
    }
}

// Mask functions
int qrMaskBit(int mask, int r, int c) {
    if (mask == 0) return ((r + c) % 2) == 0;
    if (mask == 1) return (r % 2) == 0;
    if (mask == 2) return (c % 3) == 0;
    if (mask == 3) return ((r + c) % 3) == 0;
    if (mask == 4) return (((r / 2) + (c / 3)) % 2) == 0;
    if (mask == 5) return (((r * c) % 2) + ((r * c) % 3)) == 0;
    if (mask == 6) return ((((r * c) % 2) + ((r * c) % 3)) % 2) == 0;
    if (mask == 7) return ((((r + c) % 2) + ((r * c) % 3)) % 2) == 0;
    return 0;
}

// XOR the mask onto data modules only. Function modules are not touched.
void qrApplyMask(int mask) {
    int r, c;
    for (r = 0; r < QR_SIZE; r++) {
        for (c = 0; c < QR_SIZE; c++) {
            if (qrIsFn(r, c) == 0 && qrMaskBit(mask, r, c)) {
                int v = qrGetMod(r, c) ^ 1;
                qrSetMod(r, c, v);
            }
        }
    }
}

// Format info encoding (BCH(15,5)). Returns the 15-bit format info string
// for (ecc, mask), already XORed with the mask 0x5412.
int qrEncodeFormat(int ecc, int mask) {
    int data = (qrEccBits(ecc) << 3) | (mask & 7);
    int rem = data;
    int i;
    for (i = 0; i < 10; i++) {
        rem = rem << 1;
        if (rem & 0x400) rem = rem ^ QR_BCH_GEN_FORMAT;
    }
    int bits = ((data << 10) | rem) ^ QR_BCH_MASK_FORMAT;
    return bits & 0x7FFF;
}

// Place (or clear) the 15 format-info bits in both copies. Each bit appears
// in two cells: one in column 8 ("vertical") and one in row 8 ("horizontal").
// Placement matches the QR Code 2005 specification (Figure 19).
void qrWriteFormatBits(int bits) {
    int i;
    for (i = 0; i < 15; i++) {
        int b = (bits >> i) & 1;
        int r;
        if (i < 6)      r = i;
        else if (i < 8) r = i + 1;
        else            r = QR_SIZE - 15 + i;
        qrSetMod(r, 8, b);
        int c;
        if (i < 8)      c = QR_SIZE - 1 - i;
        else if (i < 9) c = 7;
        else            c = 14 - i;
        qrSetMod(8, c, b);
    }
    qrSetMod(QR_SIZE - 8, 8, 1);  // always-dark module
}

void qrPlaceFormatInfo(int ecc, int mask) {
    qrWriteFormatBits(qrEncodeFormat(ecc, mask));
}

void qrClearFormatInfo() {
    qrWriteFormatBits(0);
    qrSetMod(QR_SIZE - 8, 8, 1);
}

// Version info encoding (V7+)
int qrEncodeVersion(int version) {
    int rem = version;
    int i;
    for (i = 0; i < 12; i++) {
        rem = rem << 1;
        if (rem & 0x1000) rem = rem ^ QR_BCH_GEN_VERSION;
    }
    return ((version << 12) | rem) & 0x3FFFF;
}

void qrPlaceVersionInfo(int version) {
    if (version < 7) return;
    int bits = qrEncodeVersion(version);
    int i;
    for (i = 0; i < 18; i++) {
        int b = (bits >> i) & 1;
        int a = QR_SIZE - 11 + (i % 3);
        int d = i / 3;
        qrSetMod(a, d, b);
        qrSetMod(d, a, b);
    }
}

// Penalty scoring (rule N1..N4 from the QR spec).
int qrPenaltyN1Run(int isRow, int idx) {
    int run = 0;
    int prev = -1;
    int penalty = 0;
    int i;
    for (i = 0; i < QR_SIZE; i++) {
        int v = isRow ? qrGetMod(idx, i) : qrGetMod(i, idx);
        if (v == prev) {
            run++;
            if (run == 5) penalty += 3;
            else if (run > 5) penalty += 1;
        } else {
            run = 1;
            prev = v;
        }
    }
    return penalty;
}

int qrPenaltyN1() {
    int total = 0;
    int i;
    for (i = 0; i < QR_SIZE; i++) {
        total += qrPenaltyN1Run(1, i);
        total += qrPenaltyN1Run(0, i);
    }
    return total;
}

int qrPenaltyN2() {
    int total = 0;
    int r, c;
    for (r = 0; r < QR_SIZE - 1; r++) {
        for (c = 0; c < QR_SIZE - 1; c++) {
            int v = qrGetMod(r, c);
            if (v == qrGetMod(r, c + 1) &&
                v == qrGetMod(r + 1, c) &&
                v == qrGetMod(r + 1, c + 1)) {
                total += 3;
            }
        }
    }
    return total;
}

// Detect 11-module patterns "10111010000" or "00001011101" in row/col.
int qrPenaltyN3LineMatch(int v0, int v1, int v2, int v3, int v4,
                         int v5, int v6, int v7, int v8, int v9, int v10) {
    int hits = 0;
    if (v0 == 1 && v1 == 0 && v2 == 1 && v3 == 1 && v4 == 1 &&
        v5 == 0 && v6 == 1 && v7 == 0 && v8 == 0 && v9 == 0 && v10 == 0) hits++;
    if (v0 == 0 && v1 == 0 && v2 == 0 && v3 == 0 && v4 == 1 &&
        v5 == 0 && v6 == 1 && v7 == 1 && v8 == 1 && v9 == 0 && v10 == 1) hits++;
    return hits;
}

int qrPenaltyN3() {
    int total = 0;
    int r, c;
    for (r = 0; r < QR_SIZE; r++) {
        for (c = 0; c <= QR_SIZE - 11; c++) {
            total += 40 * qrPenaltyN3LineMatch(
                qrGetMod(r, c), qrGetMod(r, c+1), qrGetMod(r, c+2),
                qrGetMod(r, c+3), qrGetMod(r, c+4), qrGetMod(r, c+5),
                qrGetMod(r, c+6), qrGetMod(r, c+7), qrGetMod(r, c+8),
                qrGetMod(r, c+9), qrGetMod(r, c+10));
        }
    }
    for (c = 0; c < QR_SIZE; c++) {
        for (r = 0; r <= QR_SIZE - 11; r++) {
            total += 40 * qrPenaltyN3LineMatch(
                qrGetMod(r, c), qrGetMod(r+1, c), qrGetMod(r+2, c),
                qrGetMod(r+3, c), qrGetMod(r+4, c), qrGetMod(r+5, c),
                qrGetMod(r+6, c), qrGetMod(r+7, c), qrGetMod(r+8, c),
                qrGetMod(r+9, c), qrGetMod(r+10, c));
        }
    }
    return total;
}

int qrPenaltyN4() {
    int total = QR_SIZE * QR_SIZE;
    int dark = 0;
    int r, c;
    for (r = 0; r < QR_SIZE; r++) {
        for (c = 0; c < QR_SIZE; c++) {
            if (qrGetMod(r, c) == 1) dark++;
        }
    }
    int percent10 = (dark * 200) / total;
    int dev2 = percent10 - 100;
    if (dev2 < 0) dev2 = -dev2;
    int k = dev2 / 10;
    return k * 10;
}

int qrComputePenalty() {
    return qrPenaltyN1() + qrPenaltyN2() + qrPenaltyN3() + qrPenaltyN4();
}

// Mask selection: try all 8 masks, keep the lowest-penalty one.
int qrSelectBestMask(int ecc) {
    int bestMask = 0;
    int bestPenalty = -1;
    int m;
    for (m = 0; m < 8; m++) {
        qrApplyMask(m);
        qrPlaceFormatInfo(ecc, m);
        int p = qrComputePenalty();
        if (bestPenalty < 0 || p < bestPenalty) {
            bestPenalty = p;
            bestMask = m;
        }
        qrApplyMask(m);     // XOR is involutive: undoes the mask
        qrClearFormatInfo();
    }
    return bestMask;
}

// Serialize matrix to "0/1" string lines.
void qrSerializeMatrix() {
    int r, c;
    QR_OUTPUT_LINES_COUNT = QR_SIZE;
    for (r = 0; r < QR_SIZE; r++) {
        string line = "";
        for (c = 0; c < QR_SIZE; c++) {
            line += qrGetMod(r, c) ? "1" : "0";
        }
        QR_OUTPUT_LINES[r] = line;
    }
}

// -------------------------------------------------------------------------
// 5. Public API
// -------------------------------------------------------------------------

// Last error code (for diagnostics).
//   0  : success
//  -1  : data too long for supported versions
//  -2  : unsupported mode
//  -3  : unsupported ECC level
//  -4  : encoding failure
int QR_LAST_ERROR = 0;

int qrGenerate(string data, int ecc, int mode) {
    QR_LAST_ERROR = 0;

    if (mode != MODE_BYTE) {
        QR_LAST_ERROR = -2;
        return -1;
    }
    if (ecc != ECC_L) {
        QR_LAST_ERROR = -3;
        return -1;
    }

    int dataLen = strlen(data);
    int version = qrChooseVersion(dataLen, mode, ecc);
    if (version < 0) {
        QR_LAST_ERROR = -1;
        return -1;
    }

    qrGfInit();

    if (qrEncodeData(data, mode, version) != 0) {
        QR_LAST_ERROR = -4;
        return -1;
    }
    qrPadAndPack(qrDataCodewords(version, ecc));
    qrSplitBlocks(version, ecc);
    qrComputeEcAllBlocks(version, ecc);
    qrInterleave();

    qrInitMatrix(version);
    qrPlaceFinders();
    qrPlaceTiming();
    qrPlaceAlignments(version);
    qrReserveFormatInfo();
    qrReserveVersionInfo(version);
    qrPlaceDataCodewords();
    // Version info bits are static for a given version; place them before
    // mask selection so the penalty score reflects the final matrix state.
    qrPlaceVersionInfo(version);

    int bestMask = qrSelectBestMask(ecc);
    qrApplyMask(bestMask);
    qrPlaceFormatInfo(ecc, bestMask);

    qrSerializeMatrix();
    return QR_OUTPUT_LINES_COUNT;
}

// =========================================================================
// End of native QR Code generation engine
// =========================================================================

// Global variables
string VERSION = "1.2.0";
string LANG;  // Current language code

// Context constants and variable
enum {
    CONTEXT_BOARD,
    CONTEXT_SCHEMATIC,
    CONTEXT_PACKAGE,
    CONTEXT_SYMBOL
};
int currentContext;

// Arrays for localization
string TextKeys[];    // Store keys
string TextValues[];  // Store corresponding values
int TextCount = 0;    // Number of texts loaded

// After the global variables section, add these constants and variables
enum {
    UNIT_MILS,
    UNIT_INCHES,
    UNIT_MM
};

int currentUnit = UNIT_MILS;  // Default to mils
string UnitNames[] = {"mils", "inches", "mm"};

// Function to get default grid unit and scale
int getDefaultGridUnit() {
    if (board) {
        board(B) {
            int displayUnit = B.grid.unit;
            switch(displayUnit) {
                case 0:  // GRID_UNIT_MIC
                    return UNIT_MM;
                case 1:  // GRID_UNIT_MM
                    return UNIT_MM;
                case 2:  // GRID_UNIT_MIL
                    return UNIT_MILS;
                case 3:  // GRID_UNIT_INCH
                    return UNIT_INCHES;
            }
        }
    } else if (library) {
        library(L) {
            int displayUnit = L.grid.unit;
            switch(displayUnit) {
                case 0:  // GRID_UNIT_MIC
                    return UNIT_MM;
                case 1:  // GRID_UNIT_MM
                    return UNIT_MM;
                case 2:  // GRID_UNIT_MIL
                    return UNIT_MILS;
                case 3:  // GRID_UNIT_INCH
                    return UNIT_INCHES;
            }
        }
    } else if (schematic) {
        schematic(S) {
            int displayUnit = S.grid.unit;
            switch(displayUnit) {
                case 0:  // GRID_UNIT_MIC
                    return UNIT_MM;
                case 1:  // GRID_UNIT_MM
                    return UNIT_MM;
                case 2:  // GRID_UNIT_MIL
                    return UNIT_MILS;
                case 3:  // GRID_UNIT_INCH
                    return UNIT_INCHES;
            }
        }
    }
    return UNIT_MILS;
}

// Function to convert size to mils based on selected unit
int convertToMils(real size, int fromUnit) {
    switch(fromUnit) {
        case UNIT_MM:
            return round(size * 39.3701);  // mm to mils (1 mm = 39.3701 mils)
        case UNIT_INCHES:
            return round(size * 1000.0);   // inches to mils (1 inch = 1000 mils)
        case UNIT_MILS:
            return round(size);
    }
    return round(size);
}

// Function to convert size from mils to selected unit
real convertFromMils(int size, int toUnit) {
    switch(toUnit) {
        case UNIT_MM:
            return real(size) / 39.3701;   // mils to mm
        case UNIT_INCHES:
            return real(size) / 1000.0;    // mils to inches
        case UNIT_MILS:
            return real(size);
    }
    return real(size);
}

// Function to get localized text by key
string getText(string key) {
    for (int i = 0; i < TextCount; i++) {
        if (TextKeys[i] == key) {
            return TextValues[i];
        }
    }
    return key;  // Return key if text not found
}

// Function to add text to arrays
void addText(string key, string value) {
    TextKeys[TextCount] = key;
    TextValues[TextCount] = value;
    TextCount++;
}

// Initialize the in-memory localization table for the user's language.
//
// The texts are embedded directly into this ULP so that the program is
// fully self-contained: no external CSV is downloaded, no temporary file
// is written, and no network call is performed. Languages match the set
// already supported by the project (en, fr, de, es, it, ja, ko, pl, pt,
// zh, tr). Any unrecognized language code falls back to English.
//
// Only the keys actually consumed by the dialog code are populated here.
// If a translation for a given language is missing for a key, getText()
// will gracefully return the key itself (keeping the UI usable in any
// edge case rather than producing an empty label).
void initLocalizedTexts() {
    LANG = language();
    if (LANG == "") LANG = "en";

    TextCount = 0;

    if (LANG == "fr") {
        addText("TITLE",               "Générateur de QR Code");
        addText("SETTINGS_GROUP",      "Paramètres du QR Code");
        addText("URL_LABEL",           "Entrez l'URL de votre QR code :");
        addText("SIZE_LABEL",          "Entrez la taille (0.25-5.0 pouces / 250-5000 mils / 6.35-127 mm) :");
        addText("LAYER_LABEL",         "Sélectionnez la couche :");
        addText("POSITION_NOTE",       "Le QR code sera automatiquement placé dans le quadrant supérieur gauche.");
        addText("ERROR_NO_URL",        "Aucune URL fournie. Opération annulée.");
        addText("ERROR_QR_GENERATION", "Erreur : La génération du QR code a échoué");
        addText("BUTTON_OK",           "OK");
        addText("BUTTON_CANCEL",       "Annuler");
    }
    else if (LANG == "de") {
        addText("TITLE",               "QR-Code-Generator");
        addText("SETTINGS_GROUP",      "QR-Code-Einstellungen");
        addText("URL_LABEL",           "Geben Sie die URL für Ihren QR-Code ein:");
        addText("SIZE_LABEL",          "Größe eingeben (0.25-5.0 Zoll / 250-5000 mils / 6.35-127 mm):");
        addText("LAYER_LABEL",         "Ebene auswählen:");
        addText("POSITION_NOTE",       "Der QR-Code wird automatisch im oberen linken Quadranten platziert.");
        addText("ERROR_NO_URL",        "Keine URL angegeben. Vorgang abgebrochen.");
        addText("ERROR_QR_GENERATION", "Fehler: QR-Code-Generierung fehlgeschlagen");
        addText("BUTTON_OK",           "OK");
        addText("BUTTON_CANCEL",       "Abbrechen");
    }
    else if (LANG == "es") {
        addText("TITLE",               "Generador de código QR");
        addText("SETTINGS_GROUP",      "Configuración del código QR");
        addText("URL_LABEL",           "Ingrese la URL para su código QR:");
        addText("SIZE_LABEL",          "Ingrese el tamaño (0.25-5.0 pulgadas / 250-5000 mils / 6.35-127 mm):");
        addText("LAYER_LABEL",         "Seleccione la capa:");
        addText("POSITION_NOTE",       "El código QR se colocará automáticamente en el cuadrante superior izquierdo.");
        addText("ERROR_NO_URL",        "No se proporcionó URL. Operación cancelada.");
        addText("ERROR_QR_GENERATION", "Error: Falló la generación del código QR");
        addText("BUTTON_OK",           "OK");
        addText("BUTTON_CANCEL",       "Cancelar");
    }
    else if (LANG == "it") {
        addText("TITLE",               "Generatore di codici QR");
        addText("SETTINGS_GROUP",      "Impostazioni codice QR");
        addText("URL_LABEL",           "Inserisci l'URL per il tuo codice QR:");
        addText("SIZE_LABEL",          "Inserisci dimensione (0.25-5.0 pollici / 250-5000 mils / 6.35-127 mm):");
        addText("LAYER_LABEL",         "Seleziona il layer:");
        addText("POSITION_NOTE",       "Il codice QR verrà posizionato automaticamente nel quadrante superiore sinistro.");
        addText("ERROR_NO_URL",        "Nessun URL fornito. Operazione annullata.");
        addText("ERROR_QR_GENERATION", "Errore: Generazione del codice QR fallita");
        addText("BUTTON_OK",           "OK");
        addText("BUTTON_CANCEL",       "Annulla");
    }
    else if (LANG == "ja") {
        addText("TITLE",               "QRコードジェネレーター");
        addText("SETTINGS_GROUP",      "QRコード設定");
        addText("URL_LABEL",           "QRコードのURLを入力してください：");
        addText("SIZE_LABEL",          "サイズを入力（0.25-5.0インチ / 250-5000ミル / 6.35-127 mm）：");
        addText("LAYER_LABEL",         "レイヤーを選択：");
        addText("POSITION_NOTE",       "QRコードは左上の象限に自動的に配置されます。");
        addText("ERROR_NO_URL",        "URLが提供されていません。操作がキャンセルされました。");
        addText("ERROR_QR_GENERATION", "エラー：QRコードの生成に失敗しました");
        addText("BUTTON_OK",           "OK");
        addText("BUTTON_CANCEL",       "キャンセル");
    }
    else if (LANG == "ko") {
        addText("TITLE",               "QR 코드 생성기");
        addText("SETTINGS_GROUP",      "QR 코드 설정");
        addText("URL_LABEL",           "QR 코드의 URL을 입력하세요:");
        addText("SIZE_LABEL",          "크기 입력 (0.25-5.0인치 / 250-5000밀 / 6.35-127 mm):");
        addText("LAYER_LABEL",         "레이어 선택:");
        addText("POSITION_NOTE",       "QR 코드는 자동으로 좌측 상단에 배치됩니다.");
        addText("ERROR_NO_URL",        "URL이 제공되지 않았습니다. 작업이 취소되었습니다.");
        addText("ERROR_QR_GENERATION", "오류: QR 코드 생성 실패");
        addText("BUTTON_OK",           "확인");
        addText("BUTTON_CANCEL",       "취소");
    }
    else if (LANG == "pl") {
        addText("TITLE",               "Generator kodów QR");
        addText("SETTINGS_GROUP",      "Ustawienia kodu QR");
        addText("URL_LABEL",           "Wprowadź adres URL dla kodu QR:");
        addText("SIZE_LABEL",          "Wprowadź rozmiar (0.25-5.0 cali / 250-5000 mils / 6.35-127 mm):");
        addText("LAYER_LABEL",         "Wybierz warstwę:");
        addText("POSITION_NOTE",       "Kod QR zostanie automatycznie umieszczony w lewym górnym kwadrancie.");
        addText("ERROR_NO_URL",        "Nie podano adresu URL. Operacja anulowana.");
        addText("ERROR_QR_GENERATION", "Błąd: Generowanie kodu QR nie powiodło się");
        addText("BUTTON_OK",           "OK");
        addText("BUTTON_CANCEL",       "Anuluj");
    }
    else if (LANG == "pt") {
        addText("TITLE",               "Gerador de código QR");
        addText("SETTINGS_GROUP",      "Configurações do código QR");
        addText("URL_LABEL",           "Digite a URL para seu código QR:");
        addText("SIZE_LABEL",          "Digite o tamanho (0.25-5.0 polegadas / 250-5000 mils / 6.35-127 mm):");
        addText("LAYER_LABEL",         "Selecione a camada:");
        addText("POSITION_NOTE",       "O código QR será automaticamente colocado no quadrante superior esquerdo.");
        addText("ERROR_NO_URL",        "URL não fornecida. Operação cancelada.");
        addText("ERROR_QR_GENERATION", "Erro: Falha na geração do código QR");
        addText("BUTTON_OK",           "OK");
        addText("BUTTON_CANCEL",       "Cancelar");
    }
    else if (LANG == "zh" || LANG == "zh-CN" || LANG == "zh-TW") {
        addText("TITLE",               "二维码生成器");
        addText("SETTINGS_GROUP",      "二维码设置");
        addText("URL_LABEL",           "输入您的二维码URL：");
        addText("SIZE_LABEL",          "输入尺寸（0.25-5.0英寸 / 250-5000密耳 / 6.35-127毫米）：");
        addText("LAYER_LABEL",         "选择层：");
        addText("POSITION_NOTE",       "二维码将自动放置在左上象限。");
        addText("ERROR_NO_URL",        "未提供URL。操作已取消。");
        addText("ERROR_QR_GENERATION", "错误：二维码生成失败");
        addText("BUTTON_OK",           "确定");
        addText("BUTTON_CANCEL",       "取消");
    }
    else if (LANG == "tr") {
        addText("TITLE",               "QR Kod Üreteci");
        addText("SETTINGS_GROUP",      "QR Kod Ayarları");
        addText("URL_LABEL",           "QR kodunuz için URL girin:");
        addText("SIZE_LABEL",          "Boyutu girin (0.25-5.0 inç / 250-5000 mil / 6.35-127 mm):");
        addText("LAYER_LABEL",         "Katman seçin:");
        addText("POSITION_NOTE",       "QR kodu otomatik olarak sol üst kadrana yerleştirilecektir.");
        addText("ERROR_NO_URL",        "URL sağlanmadı. İşlem iptal edildi.");
        addText("ERROR_QR_GENERATION", "Hata: QR Kod oluşturma başarısız oldu");
        addText("BUTTON_OK",           "Tamam");
        addText("BUTTON_CANCEL",       "İptal");
    }
    else {
        addText("TITLE",               "QR Code Generator");
        addText("SETTINGS_GROUP",      "QR Code Settings");
        addText("URL_LABEL",           "Enter the URL for your QR code:");
        addText("SIZE_LABEL",          "Enter size (0.25-5.0 inches / 250-5000 mils / 6.35-127 mm):");
        addText("LAYER_LABEL",         "Select layer:");
        addText("POSITION_NOTE",       "The QR code will be automatically placed in the upper-left quadrant.");
        addText("ERROR_NO_URL",        "No URL provided. Operation cancelled.");
        addText("ERROR_QR_GENERATION", "Error: QR Code generation failed");
        addText("BUTTON_OK",           "OK");
        addText("BUTTON_CANCEL",       "Cancel");
    }
}

// Function to show help dialog
void showHelpDialog() {
    dlgDialog("Help") {
        dlgVBoxLayout {
            dlgTextView(usage);
            dlgHBoxLayout {
                dlgStretch(1);
                dlgPushButton(getText("BUTTON_OK")) dlgAccept();
                dlgStretch(1);
            }
        }
    };
}

void main(void) {
    // Initialize the embedded localization table for the user's language.
    initLocalizedTexts();

    // Initialize variables
    string Url = "";
    int Size = 500;  // Size in mils
    currentUnit = getDefaultGridUnit();  // Set initial unit based on grid preferences
    real displaySize = convertFromMils(Size, currentUnit);  // Convert for display
    
    // Layer selection (simplified to most commonly used layers)
    string LayerNames[];
    int LayerNumbers[];
    int SelectedLayer = 0;  // Initialize SelectedLayer here
    
    // Detect context and set available layers
    if (board) {
        currentContext = CONTEXT_BOARD;
        LayerNames[0] = "Top";
        LayerNames[1] = "Bottom";
        LayerNames[2] = "SilkscreenTop";
        LayerNames[3] = "SilkscreenBottom";
        LayerNames[4] = "DocumentTop";
        LayerNames[5] = "DocumentBottom";
        LayerNames[6] = "Document";
        LayerNumbers[0] = 1;
        LayerNumbers[1] = 16;
        LayerNumbers[2] = 21;
        LayerNumbers[3] = 22;
        LayerNumbers[4] = 51;
        LayerNumbers[5] = 52;
        LayerNumbers[6] = 48;
    } else if (schematic) {
        currentContext = CONTEXT_SCHEMATIC;
        LayerNames[0] = "Info";
        LayerNames[1] = "Guide";
        LayerNumbers[0] = 97;
        LayerNumbers[1] = 98;
    } else if (library) {
        if (package) {
            currentContext = CONTEXT_PACKAGE;
            LayerNames[0] = "Top";
            LayerNames[1] = "Bottom";
            LayerNames[2] = "SilkscreenTop";
            LayerNames[3] = "SilkscreenBottom";
            LayerNames[4] = "DocumentTop";
            LayerNames[5] = "DocumentBottom";
            LayerNames[6] = "Document";
            LayerNumbers[0] = 1;
            LayerNumbers[1] = 16;
            LayerNumbers[2] = 21;
            LayerNumbers[3] = 22;
            LayerNumbers[4] = 51;
            LayerNumbers[5] = 52;
            LayerNumbers[6] = 48;
        } else if (symbol) {
            currentContext = CONTEXT_SYMBOL;
            LayerNames[0] = "Symbols";
            LayerNames[1] = "Info";
            LayerNames[2] = "Guide";
            LayerNumbers[0] = 94;
            LayerNumbers[1] = 97;
            LayerNumbers[2] = 98;
        } else {
            dlgMessageBox("Error: In Library editor, this ULP must be run from either Footprint or Symbol editor.",
                         "OK");
            exit(1);
        }
    } else {
        dlgMessageBox("Error: This ULP must be run from a valid editor window.\n" +
                     "Supported contexts: Board, Schematic, Footprint, or Symbol",
                     "OK");
        exit(1);
    }
    
    // Dialog for input
    if (!dlgDialog(getText("TITLE")) {
        dlgHBoxLayout {
            dlgVBoxLayout {
                dlgGroup(getText("SETTINGS_GROUP")) {
                    dlgGridLayout {
                        dlgCell(0, 0, 0, 3) dlgLabel(getText("URL_LABEL"));
                        dlgCell(1, 0, 1, 3) dlgStringEdit(Url);
                        dlgCell(2, 0, 2, 3) dlgLabel(getText("SIZE_LABEL"));
                        dlgCell(3, 0, 3, 1) dlgRealEdit(displaySize, 0.25, 5000.0);
                        dlgCell(3, 2, 3, 3) dlgComboBox(UnitNames, currentUnit) {
                            int tempMils = convertToMils(displaySize, currentUnit);
                            displaySize = convertFromMils(tempMils, currentUnit);
                            dlgRedisplay();
                        }
                    }
                    dlgSpacing(10);
                    dlgLabel(getText("LAYER_LABEL"));
                    dlgComboBox(LayerNames, SelectedLayer);
                    dlgSpacing(10);
                    dlgLabel(getText("POSITION_NOTE"));
                }
                dlgSpacing(10);
                dlgHBoxLayout {
                    dlgStretch(1);
                    dlgPushButton("+" + getText("BUTTON_OK")) dlgAccept();
                    dlgPushButton("-" + getText("BUTTON_CANCEL")) dlgReject();
                    dlgStretch(1);
                }
                dlgHBoxLayout {
                    string versionText;
                    sprintf(versionText, "v%s", VERSION);
                    dlgLabel(versionText);
                    dlgStretch(1);
                    dlgPushButton("?") {
                        showHelpDialog();
                    }
                }
            }
        }
    } || Url == "") {
        dlgMessageBox(getText("ERROR_NO_URL"));
        exit(0);
    }
    
    // Convert final size to mils for QR code generation
    Size = convertToMils(displaySize, currentUnit);
    
    // Debug dialog
    int displayUnit = 0;  // Default to MICRON
    if (board) {
        board(B) displayUnit = B.grid.unit;
    } else if (library) {
        library(L) displayUnit = L.grid.unit;
    } else if (schematic) {
        schematic(S) displayUnit = S.grid.unit;
    }
    
    // Prepare script output file. The QR matrix itself is generated locally.
    string scriptFile = filedir(argv[0]) + "qr_script.scr";
    
    // Generate the QR code matrix natively (no network, no Python).
    int nLines = qrGenerate(Url, ECC_L, MODE_BYTE);
    if (nLines <= 0) {
        string err;
        if (QR_LAST_ERROR == -1) {
            sprintf(err, "%s\n\nThe URL is too long for the supported QR versions (V1-V10, ECC L).\n" +
                         "Please use a shorter URL or wait for a future release with extended version support.",
                    getText("ERROR_QR_GENERATION"));
        } else {
            sprintf(err, "%s\n\nDebug info:\n- ULP Version: %s\n- Internal error code: %d",
                    getText("ERROR_QR_GENERATION"), VERSION, QR_LAST_ERROR);
        }
        dlgMessageBox(err, "OK");
        exit(1);
    }
    
    // Reuse the local lines[] consumed by the Eagle script generation block.
    string lines[];
    int li;
    for (li = 0; li < nLines; li++) {
        lines[li] = QR_OUTPUT_LINES[li];
    }
    
    // Generate Eagle script
    output(scriptFile, "wD") {
        int qrSize = nLines;
        real moduleScale;
        real startXoffset;
        real startX = 0;
        real startY = 0;
        
        // Calculate module size and offset based on grid unit
        switch(displayUnit) {
            case 1:  // GRID_UNIT_MM
                // Keep size in mm
                moduleScale = (real(Size) * 0.0254) / real(qrSize);  // Convert target size from mils to mm
                startXoffset = 6.35;  // 250 mils = 6.35 mm
                break;
                
            case 2:  // GRID_UNIT_MIL
                // Keep in mils
                moduleScale = real(Size) / real(qrSize);
                startXoffset = 250.0;
                break;
                
            case 3:  // GRID_UNIT_INCH
                // Convert to inches
                moduleScale = (real(Size) / 1000.0) / real(qrSize);  // Convert target size from mils to inches
                startXoffset = 0.25;  // 250 mils = 0.25 inches
                break;
                
            default:
                // Fallback to mils
                moduleScale = real(Size) / real(qrSize);
                startXoffset = 250.0;
        }

        // Determine if bottom layer
        int isBottomLayer = (currentContext == CONTEXT_BOARD || currentContext == CONTEXT_PACKAGE) &&
                           (LayerNumbers[SelectedLayer] == 16 ||  // Bottom layer
                            LayerNumbers[SelectedLayer] == 22 ||  // Bottom silkscreen
                            LayerNumbers[SelectedLayer] == 52);   // Bottom documentation

        // Adjust startX based on layer
        startX = isBottomLayer ? startXoffset : -(moduleScale * qrSize + startXoffset);

        printf("# QR Code Generator Script\n");
        printf("CHANGE LAYER %d;\n", LayerNumbers[SelectedLayer]);
        printf("SET WIRE_BEND 2;\n");

        // Generate QR code rectangles in native grid units
        for (int row = 0; row < nLines; row++) {
            string line = lines[row];
            for (int col = 0; col < strlen(line); col++) {
                if (line[col] == '1') {
                    real x1 = startX + (col * moduleScale);
                    real y1 = startY + (row * moduleScale);
                    real x2 = x1 + moduleScale;
                    real y2 = y1 + moduleScale;

                    // Mirror X coordinates if bottom layer
                    if (isBottomLayer) {
                        real temp_x1 = x1;
                        x1 = -x2;
                        x2 = -temp_x1;
                    }

                    // Use %.4f for better precision
                    printf("RECT (%.4f %.4f) (%.4f %.4f);\n", x1, y1, x2, y2);
                }
            }
        }
    }
    
    // Execute script and exit
    exit("SCRIPT '" + scriptFile + "'");
}
